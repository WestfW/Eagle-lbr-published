#usage "<qt><b>layertoggle.ulp layernum"
      "<p>Toggle visibility of the specified layer"
      "<p>"
      "<author>Author: Bill Westfield westfw@yahoo.com</author></qt>"

int mylayer;

void display (string s) {
  dlgMessageBox(s);
  return;
}

if (argc < 2) {			/* Should be ulp + arg */
    string foo="";
    sprintf(foo, "Not enough aruguments.\n"
	    "Usually used from menus like:\n"
	    "   run toglay <layernum> [<layernum2> ...]");
    display(foo);
    exit("");
}

mylayer = strtod(argv[1]);

if (board) board(B) {
   B.layers(L) {
       if (L.number == mylayer) {
	   if (L.visible) {
	       exit("display -" + L.name +";");
	   } else {
	       exit("display " + L.name+ ";");
	   }
       }
   }
}
