#usage "<qt><b>circle.ulp"
       "<p>This ulp draws circles with a specified diameter."
       "<p>\n"
       "<author>Author: Bill Westfield westfw@yahoo.com</author></qt>"

string cmdstart = "grid mm; ";
string h;
real circdia;

if (board) board(B) {
   int Result = dlgDialog("Circle") {
      dlgLabel(usage);
      dlgLabel("Circle diameter\nmm");
      dlgHBoxLayout {
         dlgRealEdit(circdia);
         dlgStretch(1);
         dlgPushButton("+&OK") dlgAccept();
         dlgStretch(1);
         dlgPushButton("-&Cancel") dlgReject();
         }
      };
   if (!Result) exit (0);
   sprintf(h, "circle (0 0) (0 %f); move (0 %f)", circdia/2, circdia/2);
   cmdstart += h;
   exit (cmdstart);
}
